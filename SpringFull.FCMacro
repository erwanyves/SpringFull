# -*- coding: utf-8 -*-
# Auteur  : Yves Guillou
# Licence : LGPL-2.1 — voir le fichier LICENSE du dépôt
"""
Lanceur pour SpringFull - Placez ce fichier dans votre dossier Macro FreeCAD
puis lancez-le depuis le menu Macro > Macros...

Version: 1.2.0
"""

import os
import sys

# Ajouter le dossier SpringFull au path
macro_dir = os.path.dirname(os.path.abspath(__file__))
springfull_dir = os.path.join(macro_dir, 'SpringFull')

# Dossier Macro EN TETE de sys.path, paquet purge du cache (11/10/2026).
# La macro importe le paquet `SpringFull.*`. Depuis FreeCAD 1.2 / 26.x, le
# dossier macro PAR VERSION (...\FreeCAD\v26-3\Macro) est aussi sur sys.path,
# AVANT ce dossier-ci, et la migration y a recopie une ANCIENNE version de
# SpringFull : c'est elle qui etait importee (ImportError showStatusMessage).
# Meme manoeuvre que les lanceurs ORing, SmartFinder et Swaging.
for _p in (springfull_dir, macro_dir):
    while _p in sys.path:
        sys.path.remove(_p)
    sys.path.insert(0, _p)
for _nom in [n for n in sys.modules if n.startswith('SpringFull')]:
    del sys.modules[_nom]

# Lancer la macro principale
# encoding EXPLICITE (14/09/2026) : sans lui, `open()` prend l'encodage
# systeme -- cp1252 sous Windows -- et tout litteral accentue de la macro
# s'affiche en mojibake (« gÃ©omÃ©trie »). Mesure : journal utilisateur.
exec(open(os.path.join(springfull_dir, 'SpringFull.FCMacro'),
          encoding='utf-8').read())
